'*********************************************
'https://github.com/rchurakov/InventorAutomation/iLogicRules/Part
'---------------------------------------------
'AddUserParameters.iLogicVb v1.0
'Created by R.Churakov 2021
'---------------------------------------------
'The rule creates 4 parameters in User
'Parameters collection for rolled tubes
'(square and rectangle) which names match with
'parameters names in content center tubes
'*********************************************

Sub Main()
	
	'Check whether it's part document
	If ThisApplication.ActiveDocument.DocumentType <> kPartDocumentObject Then
		MessageBox.Show("Can't create Parameters. A part must be active.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't set Parameters because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active part not reserved by you.", "iLogic: No permision for write", _
								MessageBoxButtons.OK, MessageBoxIcon.Warning, MessageBoxDefaultButton.Button1)
				Exit Sub
			End If
		Else
			MessageBox.Show("To save changes you need to checkout part.", "iLogic: File not reserved", _
						MessageBoxButtons.OK, MessageBoxIcon.Asterisk, MessageBoxDefaultButton.Button1)
		End If
	End If
	
	'Get the User parameters collection
	Dim userParams As UserParameters
	userParams = ThisApplication.ActiveDocument.ComponentDefinition.Parameters.UserParameters

	'Create User parameters
	CreateFrameParameter(userParams, "G_W", "Width", False)
	CreateFrameParameter(userParams, "G_H", "Depth", False)
	CreateFrameParameter(userParams, "G_T", "Thickness", False)
	CreateFrameParameter(userParams, "G_L", "Length", True)

End Sub


Sub CreateFrameParameter(parametersSet As UserParameters, paramName As String, paramComment As String, paramAsProperty As Boolean)
	Dim someParameter As Parameter
	Try
		'Check if the parameter exists
		someParameter = parametersSet.Item(paramName)
		MessageBox.Show("Parameter already exist:" & vbNewLine & paramName & " = " & someParameter.Expression, "iLogic: Parameter not created", _
						MessageBoxButtons.OK, MessageBoxIcon.Asterisk, MessageBoxDefaultButton.Button1)
	Catch
		'Add parameter to collection
		someParameter = parametersSet.AddByExpression(paramName, "1 mm", UnitsTypeEnum.kDefaultDisplayLengthUnits)
		'Add parameter comment
		someParameter.Comment = paramComment
		'Set visibility in iProperties Custom collection
		someParameter.ExposedAsProperty = paramAsProperty
	End Try
End Sub
