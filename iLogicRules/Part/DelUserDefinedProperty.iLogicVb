'*********************************************
'https://github.com/rchurakov/InventorAutomation/iLogicRules/Part
'---------------------------------------------
'DelUserDefinedProperty.iLogicVb v1.0
'Created by R.Churakov 2021
'---------------------------------------------
'The rule removes a property with specified
'name in iProperties Custom tab.
'*********************************************

Sub Main()

	'Check whether it's part document
	If ThisApplication.ActiveDocument.DocumentType <> kPartDocumentObject Then
		MessageBox.Show("A part must be active.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't create Properties because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active part not reserved by you.", "iLogic: No permision for write", _
								MessageBoxButtons.OK, MessageBoxIcon.Warning, MessageBoxDefaultButton.Button1)
				Exit Sub
			End If
		Else
			MessageBox.Show("To save changes you need to checkout part.", "iLogic: File not reserved", _
						MessageBoxButtons.OK, MessageBoxIcon.Asterisk, MessageBoxDefaultButton.Button1)
		End If
	End If
	
	'Get the User Custom property set
	Dim userCustomPropSet As PropertySet
	userCustomPropSet = ThisApplication.ActiveDocument.PropertySets.Item("User Defined Properties")
	
	'******************************************
	'* Set the name of existing property here *
	'******************************************
	Dim somePropertyName As String = "Some property"
	'******************************************
	
	Try
		Dim someProperty As Inventor.Property
		'Check if the property exists
		someProperty = userCustomPropSet.Item(somePropertyName)
		'Remove property from set
		someProperty.Delete
	Catch
		MessageBox.Show("Property «" & somePropertyName & "» does not exist.", "iLogic: Property not removed", _
						MessageBoxButtons.OK, MessageBoxIcon.Exclamation, MessageBoxDefaultButton.Button1)
	End Try
	
End Sub
