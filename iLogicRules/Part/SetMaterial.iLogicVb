'*********************************************
'https://github.com/rchurakov/InventorAutomation/iLogicRules/Part
'---------------------------------------------
'SetMaterial.iLogicVb v1.0
'Created by R.Churakov 2022
'---------------------------------------------
'The rule changes material of the active
'part. The new material name is stored in the
'variable «nextMaterialName».
'*********************************************

Sub Main()
	
	'Check whether it's part document
	If ThisApplication.ActiveDocument.DocumentType <> kPartDocumentObject Then
		MessageBox.Show("A part must be active.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't modify part because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active part not reserved by you.", "iLogic: No permision for write", _
								MessageBoxButtons.OK, MessageBoxIcon.Warning, MessageBoxDefaultButton.Button1)
				Exit Sub
			End If
		Else
			MessageBox.Show("To save changes you need to checkout part.", "iLogic: File not reserved", _
						MessageBoxButtons.OK, MessageBoxIcon.Asterisk, MessageBoxDefaultButton.Button1)
		End If
	End If
	
	'Get active part document
	Dim activePart As PartDocument
	activePart = ThisApplication.ActiveDocument
	
	'******************************
	'* Set here new material name *
	'******************************
	Dim nextMaterialName As String = "Stainless steel"
	'------------------------------
	Dim nextMaterial As Material
	Try
		nextMaterial = activePart.Materials.Item(nextMaterialName)
	Catch
		MessageBox.Show("Can't find material «" & nextMaterialName & "».", "iLogic: Material not found", _
						MessageBoxButtons.OK, MessageBoxIcon.Warning, MessageBoxDefaultButton.Button1)
		Exit Sub
	End Try
	'******************************
	
	'Check if the new material is now active
	If nextMaterial.InUse() Then
		MessageBox.Show("«" & nextMaterialName & "» already set.", "iLogic: Material not changed", _
						MessageBoxButtons.OK, MessageBoxIcon.Warning, MessageBoxDefaultButton.Button1)
		Exit Sub
	End If
	
	'Assign new material to the part.
	activePart.ComponentDefinition.Material = nextMaterial
	
	'Update mass in iProperties through Command manager
	ThisApplication.CommandManager.ControlDefinitions.Item("AppUpdateMassPropertiesCmd").Execute
	
End Sub
