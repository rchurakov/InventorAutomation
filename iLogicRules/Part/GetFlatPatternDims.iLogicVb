'*********************************************
'https://github.com/rchurakov/InventorAutomation/iLogicRules/Part
'---------------------------------------------
'GetFlatPatternDims.iLogicVb v2.0
'Created by R.Churakov 2019
'---------------------------------------------
'The rule creates 3 parameters in User
'Parameters collection that describes
'dimensions of flat pattern
'*********************************************

Sub Main()

	'Check whether it's sheet metal part document
	If ThisApplication.ActiveDocument.SubType <> "{9C464203-9BAE-11D3-8BAD-0060B0CE6BB4}" Then
		MessageBox.Show("A sheet metal part must be active.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't create Parameters because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active part not reserved by you.", "iLogic: No permision for write", _
								MessageBoxButtons.OK, MessageBoxIcon.Warning, MessageBoxDefaultButton.Button1)
				Exit Sub
			End If
		Else
			MessageBox.Show("To save changes you need to checkout part.", "iLogic: File not reserved", _
						MessageBoxButtons.OK, MessageBoxIcon.Asterisk, MessageBoxDefaultButton.Button1)
		End If
	End If
	
	'Check if the active document has a flat pattern
	If Not ThisApplication.ActiveDocument.ComponentDefinition.HasFlatPattern() Then
		MessageBox.Show("Can't create Parameters because no flat pattern.", "iLogic: No flat pattern", _
						MessageBoxButtons.OK, MessageBoxIcon.Warning, MessageBoxDefaultButton.Button1)
		Exit Sub
	End If
	
	'Get the User parameters collection
	Dim userParams As UserParameters
	userParams = ThisApplication.ActiveDocument.ComponentDefinition.Parameters.UserParameters
	
	'Get dims of flat pattern
	Dim flatPatternLength As Double
	flatPatternLength = ThisApplication.ActiveDocument.ComponentDefinition.FlatPattern.Length()
	Dim flatPatternWidth As Double
	flatPatternWidth = ThisApplication.ActiveDocument.ComponentDefinition.FlatPattern.Width()
	Dim flatPatternHeight As Double
	flatPatternHeight = ThisApplication.ActiveDocument.ComponentDefinition.Thickness.Value()
	
	'Create custom properties and set them values
	CreateParameter(userParams, "Length", flatPatternLength, "Length", True)
	CreateParameter(userParams, "Width", flatPatternWidth, "Width", True)
	CreateParameter(userParams, "Height", flatPatternHeight, "Thickness", True)

End Sub

Sub CreateParameter(parametersSet As UserParameters, paramName As String, paramValue As Object, paramComment As String, paramAsProperty As Boolean)
	Dim someParameter As Parameter
	Try
		'Check if the parameter exists
		someParameter = parametersSet.Item(paramName)
		MessageBox.Show("Parameter already exist:" & vbNewLine & paramName & " = " & someParameter.Expression, "iLogic: Parameter not created", _
						MessageBoxButtons.OK, MessageBoxIcon.Asterisk, MessageBoxDefaultButton.Button1)
	Catch
		'Add parameter to collection
		someParameter = parametersSet.AddByValue(paramName, paramValue, UnitsTypeEnum.kDefaultDisplayLengthUnits)
		'Add parameter comment
		someParameter.Comment = paramComment
		'Set visibility in iProperties Custom collection
		someParameter.ExposedAsProperty = paramAsProperty
	End Try
End Sub
