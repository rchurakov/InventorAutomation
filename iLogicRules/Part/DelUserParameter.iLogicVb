'*********************************************
'https://github.com/rchurakov/InventorAutomation/iLogicRules/Part
'---------------------------------------------
'DelUserParameter.iLogicVb v1.0
'Created by R.Churakov 2021
'---------------------------------------------
'The rule removes a parameter with specified
'name in User Parameters collection.
'*********************************************

Sub Main()

	'Check whether it's part document
	If ThisApplication.ActiveDocument.DocumentType <> kPartDocumentObject Then
		MessageBox.Show("A part must be active.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't modify part because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active part not reserved by you.", "iLogic: No permision for write", _
								MessageBoxButtons.OK, MessageBoxIcon.Warning, MessageBoxDefaultButton.Button1)
				Exit Sub
			End If
		Else
			MessageBox.Show("To save changes you need to checkout part.", "iLogic: File not reserved", _
						MessageBoxButtons.OK, MessageBoxIcon.Asterisk, MessageBoxDefaultButton.Button1)
		End If
	End If
	
	'Get the User parameters collection
	Dim userParams As UserParameters
	userParams = ThisApplication.ActiveDocument.ComponentDefinition.Parameters.UserParameters
	
	'**************************************
	'* Set here user parameter for delete *
	'**************************************
	Dim someParameter As Parameter
	Dim someParameterName As String = "G_W"
	'**************************************
	
	Try
		'Check if the parameter exists...
		someParameter = userParams.Item(someParameterName)
		'...and not in use
		If someParameter.InUse() Then
			MessageBox.Show("Parameter «" & someParameterName & "» in use.", "iLogic: Can't remove Parameter", _
						MessageBoxButtons.OK, MessageBoxIcon.Warning, MessageBoxDefaultButton.Button1)
		Else
			someParameter.Delete()
		End If
	Catch
		MessageBox.Show("There is no parameter «" & someParameterName & "».", "iLogic: Parameter not removed", _
						MessageBoxButtons.OK, MessageBoxIcon.Exclamation, MessageBoxDefaultButton.Button1)
	End Try
	
End Sub
