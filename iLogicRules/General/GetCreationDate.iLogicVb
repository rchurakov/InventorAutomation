'*********************************************
'https://github.com/rchurakov/InventorAutomation/iLogicRules/General
'---------------------------------------------
'GetCreationDate.iLogicVb v1.0
'Created by R.Churakov 2018
'---------------------------------------------
'The rule gets file creation date and sets it
'in iProperties Creation date property
'*********************************************

Sub Main()
	
	'Check if the active model exists
	If ThisApplication.ActiveDocument.FileSaveCounter = 0 Then
		MessageBox.Show("The model is not saved on the file system." & vbNewLine & _
						"Save the model first.", "iLogic: No creation date yet", _
						MessageBoxButtons.OK, MessageBoxIcon.Warning, MessageBoxDefaultButton.Button1)
		Exit Sub
	End If
	
	'Check if the active document is modifiable
	If Not ThisApplication.ActiveDocument.IsModifiable Then
		MessageBox.Show("Can't set a date because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active part not reserved by you.", "iLogic: No permision for write", _
								MessageBoxButtons.OK, MessageBoxIcon.Warning, MessageBoxDefaultButton.Button1)
				Exit Sub
			End If
		Else
			MessageBox.Show("To save changes you need to checkout the file.", "iLogic: File not reserved", _
						MessageBoxButtons.OK, MessageBoxIcon.Asterisk, MessageBoxDefaultButton.Button1)
		End If
	End If
	
	'Active model full file name (path + name + extension)
	Dim activeModelFullFileName As String
	activeModelFullFileName = ThisApplication.ActiveDocument.FullFileName

	'Creating file system object
	Dim oFS As Object
	oFS = CreateObject("Scripting.FileSystemObject")

	'Get system creation date
	Dim creationDate As String
	creationDate = oFS.GetFile(activeModelFullFileName).DateCreated

	'Set creation date in iProperties
	iProperties.Value("Project", "Creation Date") = creationDate

End Sub
