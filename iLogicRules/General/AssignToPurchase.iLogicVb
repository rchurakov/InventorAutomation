'*********************************************
'https://github.com/rchurakov/InventorAutomation/iLogicRules/General
'---------------------------------------------
'AssignToPurchase.iLogicVb v1.0
'Created by R.Churakov 2021
'---------------------------------------------
'The rule assigns for active model BOM
'structure type as Purchased
'*********************************************

Sub Main()
	'Check whether it's not drawing document
	If ThisApplication.ActiveDocument.DocumentType = kDrawingDocumentObject Then
		MessageBox.Show("Can't assign structure type in drawing.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't assign structure type because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active file not reserved by you.", "iLogic: No permision for write", _
								MessageBoxButtons.OK, MessageBoxIcon.Warning, MessageBoxDefaultButton.Button1)
				Exit Sub
			End If
		Else
			MessageBox.Show("To save changes you need to checkout the file.", "iLogic: File not reserved", _
						MessageBoxButtons.OK, MessageBoxIcon.Asterisk, MessageBoxDefaultButton.Button1)
		End If
	End If
	
	'Assign the purchased structure type
	ThisApplication.ActiveDocument.ComponentDefinition.BOMStructure = BOMStructureEnum.kPurchasedBOMStructure

	InventorVb.DocumentUpdate()
	
End Sub
