'*********************************************
'https://github.com/rchurakov/InventorAutomation/iLogicRules/General
'---------------------------------------------
'FileNameIntoPartNumber.iLogicVb v2.0
'Created by R.Churakov 2018
'---------------------------------------------
'The rule sets Part number on iProperties
'Project page from file name
'*********************************************

Sub Main()

	'Check if the selected model exists
	If ThisApplication.ActiveDocument.FileSaveCounter = 0 Then
		MessageBox.Show("The model is not saved on the file system." & vbNewLine & _
						"Save the model first.", "iLogic: No file name yet", _
						MessageBoxButtons.OK, MessageBoxIcon.Warning, MessageBoxDefaultButton.Button1)
		Exit Sub
	End If
	
	'Check if the active document is modifiable
	If Not ThisApplication.ActiveDocument.IsModifiable Then
		MessageBox.Show("Can't set Part number because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active file not reserved by you.", "iLogic: No permision for write", _
								MessageBoxButtons.OK, MessageBoxIcon.Warning, MessageBoxDefaultButton.Button1)
				Exit Sub
			End If
		Else
			MessageBox.Show("To save changes you need to checkout the file.", "iLogic: File not reserved", _
						MessageBoxButtons.OK, MessageBoxIcon.Asterisk, MessageBoxDefaultButton.Button1)
		End If
	End If
	
	Dim pathFilenameExt As String = ThisApplication.ActiveDocument.FullFileName
	Dim lastBackslashPosition As Integer = InStrRev(pathFilenameExt, "\", -1)
	Dim fileName As String = Mid(pathFilenameExt, lastBackslashPosition + 1, Len(pathFilenameExt) - lastBackslashPosition - 4)
	
	Dim propertyName As String = "Part Number"
	Dim propertySetName As String = "Design Tracking Properties"
	
	Dim partNumberProperty As Inventor.Property
	partNumberProperty = ThisApplication.ActiveDocument.PropertySets.Item(propertySetName).Item(propertyName)
	
	partNumberProperty.Value = fileName
	
End Sub
