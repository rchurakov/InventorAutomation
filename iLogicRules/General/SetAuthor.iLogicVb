'*********************************************
'https://github.com/rchurakov/InventorAutomation/iLogicRules/General
'---------------------------------------------
'SetAuthor.iLogicVb v2.0
'Created by R.Churakov 2018
'---------------------------------------------
'The rule sets Author on iProperties Summary
'page from User name field in Application
'Options -> General tab
'---------------------------------------------

Sub Main()
	
	'Check if the active document is modifiable
	If Not ThisApplication.ActiveDocument.IsModifiable Then
		MessageBox.Show("Can't set User name because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active file not reserved by you.", "iLogic: No permision for write", _
								MessageBoxButtons.OK, MessageBoxIcon.Warning, MessageBoxDefaultButton.Button1)
				Exit Sub
			End If
		Else
			MessageBox.Show("To save changes you need to checkout the file.", "iLogic: File not reserved", _
						MessageBoxButtons.OK, MessageBoxIcon.Asterisk, MessageBoxDefaultButton.Button1)
		End If
	End If
	
	Dim propertyName As String = "Author"
	Dim propertySetName As String = "Summary Information"
	
	Dim authorProperty As Inventor.Property
	authorProperty = ThisApplication.ActiveDocument.PropertySets.Item(propertySetName).Item(propertyName)
	
	authorProperty.Value = ThisApplication.UserName
	
End Sub


'=============================================
'Notes:
'---------------------------------------------
'[
'propertyName = "Author" (in "Summary Information" set)
'propertyName = "Authority" (in "Design Tracking Properties" set)
'propertyName = "Designer" (in "Design Tracking Properties" set)
'---------------------------------------------
'propertySetName = "Design Tracking Properties"
'propertySetName = "Summary Information"
'propertySetName = "Document Summary Information"
'propertySetName = "User Defined Properties"
']
