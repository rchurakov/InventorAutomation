'*********************************************
'https://github.com/rchurakov/InventorAutomation/iLogicRules/Assembly
'---------------------------------------------
'SaveAndReplaceWithDrw.iLogicVb v1.0
'Created by R.Churakov 2021
'---------------------------------------------
'Same as «Save and Replace Component» in
'assembly environment (Assembly tab ->
'Productivity), but with drawing associated
'with 3D model.
'The rule doesn't replace model reference in
'drawing. Use rule
'«ReplaceModelReference.iLogicVb» for this.
'*********************************************

Sub Main
	
	'Check whether it's assembly document
	If ThisApplication.ActiveDocument.DocumentType <> kAssemblyDocumentObject Then
		MessageBox.Show("An assembly must be active.", "iLogic: Wrong document type", _
						MessageBoxButtons.OK, MessageBoxIcon.Warning, MessageBoxDefaultButton.Button1)
		Exit Sub
	End If
	
	'Check if the active document is modifiable
	If Not ThisApplication.ActiveDocument.IsModifiable Then
		MessageBox.Show("Can't assign structure type because file is read-only.", "iLogic: Read-only file", _
						MessageBoxButtons.OK, MessageBoxIcon.Warning, MessageBoxDefaultButton.Button1)
		Exit Sub
	End If
	
	'Check active project type (36353 = kSingleUserMode, single user project)
	If ThisApplication.DesignProjectManager.ActiveDesignProject.ProjectType <> MultiUserModeEnum.kSingleUserMode Then
		'Check if the active document reserved for write
		If ThisApplication.ActiveDocument.ReservedForWrite() Then
			'Check if the active document reserved by the caller
			If Not ThisApplication.ActiveDocument.ReservedForWriteByMe() Then
				MessageBox.Show("Active file not reserved by you.", "iLogic: No permision for write", _
								MessageBoxButtons.OK, MessageBoxIcon.Warning, MessageBoxDefaultButton.Button1)
				Exit Sub
			End If
		Else
			MessageBox.Show("To save changes you need to checkout the file.", "iLogic: File not reserved", _
						MessageBoxButtons.OK, MessageBoxIcon.Asterisk, MessageBoxDefaultButton.Button1)
		End If
	End If
	
	'Get currently selected component
	Dim selectedModel As ComponentOccurrence
	On Error Goto NothingSelected
	selectedModel = ThisApplication.ActiveDocument.SelectSet.Item(1)

	'Processing full file name of original model
	'[
	'Get selected model document
	Dim selectedModelDoc As Document = selectedModel.Definition.Document
	'Get full file name (path + filename + extension)
	Dim fullPathSelectedModel As String = selectedModelDoc.FullFileName
	'Find last backslash position
	Dim lastBackslashPosition As String = InStrRev(fullPathSelectedModel, "\", -1)
	'Get FILENAME + EXTENSION
	Dim fullNameSelectedModel As String = Right(fullPathSelectedModel, Len(fullPathSelectedModel) - lastBackslashPosition)
	'Get FILENAME without path and extension
	Dim shortNameSelectedModel As String = Left(fullNameSelectedModel, Len(fullNameSelectedModel) - 4)
	'Get only PATH without filename and extension
	Dim pathSelectedModel As String = Left(fullPathSelectedModel, Len(fullPathSelectedModel) - Len(fullNameSelectedModel))
	']

	'Create a file dialog box Save As
	'[
	Dim saveAsFileDialog As inventor.FileDialog = Nothing
	InventorVb.Application.CreateFileDialog(saveAsFileDialog)

	'Check file type and set dialog filter
	If selectedModelDoc.DocumentType = kPartDocumentObject Then
		saveAsFileDialog.Filter = "Autodesk Inventor Part Files (*.ipt)|*.ipt"
	Else If selectedModelDoc.DocumentType = kAssemblyDocumentObject Then
		saveAsFileDialog.Filter = "Autodesk Inventor Assembly Files (*.iam)|*.iam"
	End If

	'Set the file name string to use in input box
	saveAsFileDialog.FileName = fullPathSelectedModel

	'Set the flag (True) so an error will be raised if the user clicks Cancel
	saveAsFileDialog.CancelError = True

	'Show the Save As dialog
	On Error GoTo CancelSave
	saveAsFileDialog.ShowSave()
	']

	'Check user input
	'[
	Dim newModelFileName As String
	'Catch an empty string in the input
	If saveAsFileDialog.FileName <> "" Then
		newModelFileName = saveAsFileDialog.FileName
		'Save the file
		selectedModelDoc.SaveAs(newModelFileName, True) 'True = Save As Copy; False = Save As
		'Replace the model
		selectedModel.Replace(newModelFileName, False)'True = replace all
	Else
		MessageBox.Show("File name input error.", "iLogic: Wrong file name", MessageBoxButtons.OK, _
						MessageBoxIcon.Error, MessageBoxDefaultButton.Button1)
		Exit Sub
	End If
	']

	'Checking for and saving drawing
	'[
	Dim originalDrawingPath As String
	Dim extension As String = ".idw"
	originalDrawingPath = pathSelectedModel & shortNameSelectedModel & extension

	'Find if drawing exist
	If Dir(originalDrawingPath) = "" Then
		extension = ".dwg"
		originalDrawingPath = pathSelectedModel & shortNameSelectedModel & extension
		If Dir(originalDrawingPath) = "" Then
			MessageBox.Show("Drawing not found. Only model saved.", "iLogic: No drawing", MessageBoxButtons.OK, _
								MessageBoxIcon.Warning, MessageBoxDefaultButton.Button1)
			Exit Sub
		End If
	End If

	'Open original drawing
	originalDrawing = ThisApplication.Documents.Open(originalDrawingPath, False)'False = silent mode

	'Set location for new drawing
	Dim newDrawingPath As String
	newDrawingPath = Left(newModelFileName, Len(newModelFileName) - 4) & extension

	'Saving new drawing
	originalDrawing.SaveAs(newDrawingPath, False)'False = Save As Copy; True = Save As
	originalDrawing.Close(True)'True = skip the save; False = normal save process with dialog box
	']

	InventorVb.DocumentUpdate()

	Exit Sub


	'Error handeling
	'[
	NothingSelected:
	MessageBox.Show("First select a model.", "iLogic: Nothing selected", MessageBoxButtons.OK, _
								MessageBoxIcon.Warning, MessageBoxDefaultButton.Button1)
	Exit Sub

	CancelSave:
	MessageBox.Show("Component was not replaced.", "iLogic: Operation canceled", MessageBoxButtons.OK, _
								MessageBoxIcon.Warning, MessageBoxDefaultButton.Button1)
	Exit Sub
	']
End Sub
